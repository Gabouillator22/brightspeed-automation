;;; Generated by bssheetplan.py. Safe to overwrite.
(vl-load-com)
(defun bssheet-plan-ensure-layer (lname color / )
  (if (not (tblsearch "LAYER" lname)) (command "_.LAYER" "N" lname "C" (itoa color) lname ""))
  (command "_.LAYER" "ON" lname "T" lname "")
  (princ))
(defun bssheet-plan-make-rect (verts layer / )
  (entmakex (append (list '(0 . "LWPOLYLINE") '(100 . "AcDbEntity") (cons 8 layer) '(100 . "AcDbPolyline") '(90 . 4) '(70 . 1)) (mapcar '(lambda (p) (cons 10 p)) verts))))
(defun bssheet-plan-make-text (pt ang txt layer height / )
  (entmakex (list '(0 . "TEXT") (cons 8 layer) (cons 10 pt) (cons 11 pt) (cons 40 height) (cons 1 txt) (cons 50 ang) '(72 . 1) '(73 . 2) '(7 . "STANDARD"))))
(setq *bssheet-generated-plan*
  '(
    ("S001" (2302191.928 648404.855 0.0) 0.00000000 ((2301741.928 648104.855 0.0) (2302641.928 648104.855 0.0) (2302641.928 648704.855 0.0) (2301741.928 648704.855 0.0)))
    ("S002" (2301291.928 648404.855 0.0) 0.00000000 ((2300841.928 648104.855 0.0) (2301741.928 648104.855 0.0) (2301741.928 648704.855 0.0) (2300841.928 648704.855 0.0)))
    ("S003" (2301291.928 649004.855 0.0) 0.00000000 ((2300841.928 648704.855 0.0) (2301741.928 648704.855 0.0) (2301741.928 649304.855 0.0) (2300841.928 649304.855 0.0)))
    ("S004" (2300391.928 648404.855 0.0) 0.00000000 ((2299941.928 648104.855 0.0) (2300841.928 648104.855 0.0) (2300841.928 648704.855 0.0) (2299941.928 648704.855 0.0)))
    ("S005" (2300391.928 649004.855 0.0) 0.00000000 ((2299941.928 648704.855 0.0) (2300841.928 648704.855 0.0) (2300841.928 649304.855 0.0) (2299941.928 649304.855 0.0)))
    ("S006" (2299491.928 649004.855 0.0) 0.00000000 ((2299041.928 648704.855 0.0) (2299941.928 648704.855 0.0) (2299941.928 649304.855 0.0) (2299041.928 649304.855 0.0)))
    ("S007" (2299491.928 648404.855 0.0) 0.00000000 ((2299041.928 648104.855 0.0) (2299941.928 648104.855 0.0) (2299941.928 648704.855 0.0) (2299041.928 648704.855 0.0)))
    ("S008" (2298591.928 649004.855 0.0) 0.00000000 ((2298141.928 648704.855 0.0) (2299041.928 648704.855 0.0) (2299041.928 649304.855 0.0) (2298141.928 649304.855 0.0)))
    ("S009" (2298591.928 648404.855 0.0) 0.00000000 ((2298141.928 648104.855 0.0) (2299041.928 648104.855 0.0) (2299041.928 648704.855 0.0) (2298141.928 648704.855 0.0)))
    ("S010" (2297691.928 649004.855 0.0) 0.00000000 ((2297241.928 648704.855 0.0) (2298141.928 648704.855 0.0) (2298141.928 649304.855 0.0) (2297241.928 649304.855 0.0)))
    ("S011" (2297691.928 649604.855 0.0) 0.00000000 ((2297241.928 649304.855 0.0) (2298141.928 649304.855 0.0) (2298141.928 649904.855 0.0) (2297241.928 649904.855 0.0)))
    ("S012" (2296791.928 649004.855 0.0) 0.00000000 ((2296341.928 648704.855 0.0) (2297241.928 648704.855 0.0) (2297241.928 649304.855 0.0) (2296341.928 649304.855 0.0)))
    ("S013" (2296791.928 649604.855 0.0) 0.00000000 ((2296341.928 649304.855 0.0) (2297241.928 649304.855 0.0) (2297241.928 649904.855 0.0) (2296341.928 649904.855 0.0)))
    ("S014" (2295891.928 649604.855 0.0) 0.00000000 ((2295441.928 649304.855 0.0) (2296341.928 649304.855 0.0) (2296341.928 649904.855 0.0) (2295441.928 649904.855 0.0)))
    ("S015" (2295891.928 649004.855 0.0) 0.00000000 ((2295441.928 648704.855 0.0) (2296341.928 648704.855 0.0) (2296341.928 649304.855 0.0) (2295441.928 649304.855 0.0)))
    ("S016" (2295891.928 648404.855 0.0) 0.00000000 ((2295441.928 648104.855 0.0) (2296341.928 648104.855 0.0) (2296341.928 648704.855 0.0) (2295441.928 648704.855 0.0)))
  ))
(defun c:BSSHEETMAKEPLAN ( / old-clayer old-cmdecho rec label-pt)
  (setq old-clayer (getvar "CLAYER") old-cmdecho (getvar "CMDECHO"))
  (setvar "CMDECHO" 0)
  (command "_.UNDO" "_BE")
  (bssheet-plan-ensure-layer "BS-SHEET-PROPOSED" 30)
  (bssheet-plan-ensure-layer "BS-SHEET-LABELS" 30)
  (foreach rec *bssheet-generated-plan*
    (bssheet-plan-make-rect (nth 3 rec) "BS-SHEET-PROPOSED")
    (setq label-pt (cadr rec))
    (bssheet-plan-make-text label-pt (nth 2 rec) (car rec) "BS-SHEET-LABELS" 60.000))
  (command "_.UNDO" "_E")
  (setvar "CLAYER" old-clayer)
  (setvar "CMDECHO" old-cmdecho)
  (princ "\n[BSSHEETMAKEPLAN] Created 16 proposed sheet rectangle(s).")
  (princ))
(princ "\n[BSSHEET_PLAN] Loaded. Run BSSHEETMAKEPLAN.")
(princ)
