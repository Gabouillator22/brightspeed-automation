;;; Generated by bssheetplan.py. Safe to overwrite.
(vl-load-com)
(defun bssheet-plan-ensure-layer (lname color / )
  (if (fboundp 'bs-ensure-layer) (bs-ensure-layer lname color)
    (progn (if (not (tblsearch "LAYER" lname)) (command "_.LAYER" "N" lname "C" (itoa color) lname "")) (command "_.LAYER" "ON" lname "T" lname "")))
  (princ))
(defun bssheet-plan-make-rect (verts layer / )
  (entmakex (append (list '(0 . "LWPOLYLINE") '(100 . "AcDbEntity") (cons 8 layer) '(100 . "AcDbPolyline") '(90 . 4) '(70 . 1)) (mapcar '(lambda (p) (cons 10 p)) verts))))
(defun bssheet-plan-make-text (pt ang txt layer height / )
  (entmakex (list '(0 . "TEXT") (cons 8 layer) (cons 10 pt) (cons 11 pt) (cons 40 height) (cons 1 txt) (cons 50 ang) '(72 . 1) '(73 . 2) '(7 . "STANDARD"))))
(setq *bssheet-generated-plan*
  '(
    ("S001" (2302363.031 648256.312 0.0) 1.71172146 ((2302723.263 647852.911 0.0) (2302596.850 648743.989 0.0) (2302002.798 648659.714 0.0) (2302129.212 647768.636 0.0)))
    ("S002" (2301672.831 648530.737 0.0) 3.08791837 ((2302138.278 648806.163 0.0) (2301239.574 648854.447 0.0) (2301207.385 648255.311 0.0) (2302106.089 648207.027 0.0)))
    ("S003" (2300774.354 648582.756 0.0) 3.08762678 ((2301239.881 648858.047 0.0) (2300341.191 648906.592 0.0) (2300308.828 648307.466 0.0) (2301207.517 648258.920 0.0)))
    ("S004" (2299875.529 648627.995 0.0) 3.08775598 ((2300341.020 648903.346 0.0) (2299442.324 648951.775 0.0) (2299410.038 648352.645 0.0) (2300308.734 648304.215 0.0)))
    ("S005" (2298977.177 648682.349 0.0) 3.07939457 ((2299444.954 648953.798 0.0) (2298546.694 649009.740 0.0) (2298509.400 648410.900 0.0) (2299407.659 648354.958 0.0)))
    ("S006" (2298107.354 648894.774 0.0) 2.80249596 ((2298631.520 649028.005 0.0) (2297782.770 649327.376 0.0) (2297583.189 648761.543 0.0) (2298431.939 648462.171 0.0)))
    ("S007" (2297266.346 649213.804 0.0) 2.73037926 ((2297798.749 649308.920 0.0) (2296973.776 649668.670 0.0) (2296733.943 649118.688 0.0) (2297558.916 648758.938 0.0)))
    ("S008" (2296442.507 649576.129 0.0) 2.72360865 ((2296975.541 649667.638 0.0) (2296153.023 650032.965 0.0) (2295909.472 649484.620 0.0) (2296731.990 649119.293 0.0)))
    ("S009" (2295944.862 649299.125 0.0) -1.76842411 ((2295739.057 649799.269 0.0) (2295562.347 648916.787 0.0) (2296150.668 648798.981 0.0) (2296327.378 649681.463 0.0)))
    ("S010" (2295768.153 648416.643 0.0) -1.76842411 ((2295562.347 648916.787 0.0) (2295385.638 648034.306 0.0) (2295973.959 647916.499 0.0) (2296150.668 648798.981 0.0)))
  ))
(defun c:BSSHEETMAKEPLAN ( / old-clayer old-cmdecho rec label-pt)
  (setq old-clayer (getvar "CLAYER") old-cmdecho (getvar "CMDECHO"))
  (setvar "CMDECHO" 0)
  (command "_.UNDO" "_BE")
  (bssheet-plan-ensure-layer "BS-SHEET-PROPOSED" 30)
  (bssheet-plan-ensure-layer "BS-SHEET-LABELS" 30)
  (foreach rec *bssheet-generated-plan*
    (bssheet-plan-make-rect (nth 3 rec) "BS-SHEET-PROPOSED")
    (setq label-pt (cadr rec))
    (bssheet-plan-make-text label-pt (nth 2 rec) (car rec) "BS-SHEET-LABELS" 60.000))
  (command "_.UNDO" "_E")
  (setvar "CLAYER" old-clayer)
  (setvar "CMDECHO" old-cmdecho)
  (princ "\n[BSSHEETMAKEPLAN] Created 10 proposed sheet rectangle(s).")
  (princ))
(princ "\n[BSSHEET_PLAN] Loaded. Run BSSHEETMAKEPLAN.")
(princ)
